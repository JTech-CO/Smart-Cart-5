# FreeCAD: Macro > Macros > select this file > Execute.
# Imports the same real BREP components. No external CadQuery install is required.
# This is a solid snapshot importer, not a parametric PartDesign reconstruction.
import FreeCAD as App
import Part, json
from pathlib import Path
try:
    here=Path(__file__).resolve().parent
except NameError:
    here=Path(App.getUserMacroDir())
manifest=here/'assembly-manifest.json'
if not manifest.exists():
    try: from PySide import QtGui
    except ImportError: from PySide2 import QtWidgets as QtGui
    chosen=QtGui.QFileDialog.getOpenFileName(None,'Select cad/assembly-manifest.json','','JSON (*.json)')
    if isinstance(chosen,tuple):chosen=chosen[0]
    if not chosen:raise RuntimeError('No manifest selected; nothing was imported.')
    manifest=Path(chosen);here=manifest.parent
model=json.loads((here.parent/'data/assembly.json').read_text(encoding='utf-8'))
items=json.loads(manifest.read_text(encoding='utf-8'));doc=App.newDocument('Smart_Cart_5')
groups={}
for it in items:
    cat=it['category']
    if cat not in groups:
        groups[cat]=doc.addObject('App::DocumentObjectGroup','D5_'+cat);groups[cat].Label=cat
    shape=Part.Shape();shape.read(str(here/it['file']))
    if shape.isNull() or not shape.isValid():raise RuntimeError('Invalid BREP: '+it['file'])
    o=doc.addObject('Part::Feature',it['name']);o.Label=it['ref']+' / '+it['material'];o.Shape=shape;groups[cat].addObject(o)
    o.addProperty('App::PropertyString','EvidenceStatus','D5');o.EvidenceStatus='Prototype integration; physical measurements and energization hold'
    mat=model['materials'][it['material']];color=mat['color'];o.ViewObject.ShapeColor=tuple(int(color[q:q+2],16)/255.0 for q in [1,3,5]);o.ViewObject.Transparency=round(100*(1-mat.get('alpha',1)));o.ViewObject.Visibility=cat not in ('covers','accessories')
doc.recompute()
if App.GuiUp:
    import FreeCADGui as Gui
    Gui.activeDocument().activeView().viewAxonometric();Gui.activeDocument().activeView().fitAll()
App.Console.PrintMessage('Smart-Cart-5: imported %d BREP features. Save As to keep your edits.\n'%len(items))
